module servicechainorchestrator {
    yang-version 1;
    namespace "urn:opendaylight:params:xml:ns:yang:servicechainorchestrator";
    prefix "servicechainorchestrator";

    revision "2021-04-11" {
        description "Initial revision of servicechainorchestrator model";
    } 
    
    rpc create-v-m {
    	input {
    		container  cvm {
    			list c-virtual-machine {
    				leaf name {
    					type string;
    				}
    				leaf image {
    					type string;
    				}
    				leaf flavour {
    					type int32;
    				}
    				leaf min_count {
    					type int32;
    				}
    				leaf max_count {
    					type int32;
    				}
    				leaf security_groups {
    					type string;
    				}
    				leaf key_pair {
    					type string;
    				}
    				leaf networks {
    					type string;
    				}
    				leaf host {
    					type string;
    				}
    			}
    		}
    	}
    	output {
    		leaf vm_attributes {
    			type string;
    		}
    	}
    }
    
    rpc create-service-chain {
    	input {
    		leaf name {
    			type string;
    		}
    		container vms {
    			list vm-requirement {
    				leaf int_id {
    		    		type int32;
    		    	}
    		    	leaf hostname {
    		    		type string;
    		    	}
    		    	leaf flavour {
    		    		type string;
    		    	}   	
    		    	leaf image_id {
    		    		type string;
    		    	}
    		    	leaf network_id {
    		    		type string;
    		    	}
    		    	leaf ip_address {
    		    		type string;
    		    	}
    		    }
    			list virtual-link {
    				leaf _id {
    		    		type string;
    		    	}
    		    	leaf int_id {
    		    		type int32;
    		    	}
    		    	leaf dst_node {
    		    		type int32;
    		    	}
    		    	leaf src_node {
    		    		type int32;
    		    	}   	
    		    	leaf bandwidth {
    		    		type int32;
    		    	}
    		    	leaf max_link_delay {
    		    		type int32;
    		    	}
    			}
    		}
    	}
    	output {
    		leaf greeting {
    			type string;
    		}
    	}
    }
    
    rpc hello-world {
        input {
            leaf name {
                type string;
            }
        }
        output {
            leaf greeting {
                type string;
            }
        }
    }
}
